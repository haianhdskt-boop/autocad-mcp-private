;; ==========================================================================
;; AUTOCAD AI: FULL ARCHITECTURAL DRAWING (TOWNHOUSE 5x15m - 3 FLOORS)
;; ==========================================================================
(defun c:draw_full_townhouse ()
  (setvar "CMDECHO" 0)
  (setvar "OSMODE" 0)
  (command "._ERASE" "_ALL" "")

  ;; 1. Layers Setup
  (command "._-LAYER" "_M" "KT_TUONG_220" "_C" "1" "KT_TUONG_220" "")
  (command "._-LAYER" "_M" "KT_TUONG_110" "_C" "2" "KT_TUONG_110" "")
  (command "._-LAYER" "_M" "KT_COT"       "_C" "6" "KT_COT"       "")
  (command "._-LAYER" "_M" "KT_CUA_DI"    "_C" "3" "KT_CUA_DI"    "")
  (command "._-LAYER" "_M" "KT_CUA_SO"    "_C" "4" "KT_CUA_SO"    "")
  (command "._-LAYER" "_M" "KT_THANG"     "_C" "5" "KT_THANG"     "")
  (command "._-LAYER" "_M" "KT_NOITHAT"   "_C" "8" "KT_NOITHAT"   "")
  (command "._-LAYER" "_M" "KT_TEXT"      "_C" "7" "KT_TEXT"      "")
  (command "._-LAYER" "_M" "KT_DIMS"      "_C" "9" "KT_DIMS"      "")
  (command "._-LAYER" "_M" "KT_TRUC"      "_C" "1" "KT_TRUC"      "")
  (command "._-LAYER" "_M" "KT_CANH_QUAN" "_C" "3" "KT_CANH_QUAN" "")

  ;; ----------------- TẦNG 1: MẶT BẰNG TẦNG 1 - KHÁCH BẾP MỞ & TIỂU CẢNH -----------------
  (command "._-LAYER" "_S" "KT_TUONG_220" "")
  (command "._RECTANG" (list 0.0 0.0) (list 5000.0 15000.0))
  (command "._RECTANG" (list 220.0 220.0) (list 4780.0 14780.0))
  (command "._-LAYER" "_S" "KT_COT" "")
  (command "._RECTANG" (list 0.0 0.0) (list 220.0 220.0))
  (command "._LINE" (list 0.0 0.0) (list 220.0 220.0) "")
  (command "._LINE" (list 220.0 0.0) (list 0.0 220.0) "")
  (command "._RECTANG" (list 4780.0 0.0) (list 5000.0 220.0))
  (command "._LINE" (list 4780.0 0.0) (list 5000.0 220.0) "")
  (command "._LINE" (list 5000.0 0.0) (list 4780.0 220.0) "")
  (command "._RECTANG" (list 0.0 4390.0) (list 220.0 4610.0))
  (command "._LINE" (list 0.0 4390.0) (list 220.0 4610.0) "")
  (command "._LINE" (list 220.0 4390.0) (list 0.0 4610.0) "")
  (command "._RECTANG" (list 4780.0 4390.0) (list 5000.0 4610.0))
  (command "._LINE" (list 4780.0 4390.0) (list 5000.0 4610.0) "")
  (command "._LINE" (list 5000.0 4390.0) (list 4780.0 4610.0) "")
  (command "._RECTANG" (list 0.0 10390.0) (list 220.0 10610.0))
  (command "._LINE" (list 0.0 10390.0) (list 220.0 10610.0) "")
  (command "._LINE" (list 220.0 10390.0) (list 0.0 10610.0) "")
  (command "._RECTANG" (list 4780.0 10390.0) (list 5000.0 10610.0))
  (command "._LINE" (list 4780.0 10390.0) (list 5000.0 10610.0) "")
  (command "._LINE" (list 5000.0 10390.0) (list 4780.0 10610.0) "")
  (command "._RECTANG" (list 0.0 14780.0) (list 220.0 15000.0))
  (command "._LINE" (list 0.0 14780.0) (list 220.0 15000.0) "")
  (command "._LINE" (list 220.0 14780.0) (list 0.0 15000.0) "")
  (command "._RECTANG" (list 4780.0 14780.0) (list 5000.0 15000.0))
  (command "._LINE" (list 4780.0 14780.0) (list 5000.0 15000.0) "")
  (command "._LINE" (list 5000.0 14780.0) (list 4780.0 15000.0) "")
  (command "._-LAYER" "_S" "KT_THANG" "")
  (command "._RECTANG" (list 220.0 5000.0) (list 1220.0 10500.0))
  (command "._LINE" (list 220.0 5261.9047619047615) (list 1220.0 5261.9047619047615) "")
  (command "._LINE" (list 220.0 5523.809523809524) (list 1220.0 5523.809523809524) "")
  (command "._LINE" (list 220.0 5785.714285714286) (list 1220.0 5785.714285714286) "")
  (command "._LINE" (list 220.0 6047.619047619048) (list 1220.0 6047.619047619048) "")
  (command "._LINE" (list 220.0 6309.523809523809) (list 1220.0 6309.523809523809) "")
  (command "._LINE" (list 220.0 6571.428571428572) (list 1220.0 6571.428571428572) "")
  (command "._LINE" (list 220.0 6833.333333333334) (list 1220.0 6833.333333333334) "")
  (command "._LINE" (list 220.0 7095.238095238095) (list 1220.0 7095.238095238095) "")
  (command "._LINE" (list 220.0 7357.142857142857) (list 1220.0 7357.142857142857) "")
  (command "._LINE" (list 220.0 7619.047619047619) (list 1220.0 7619.047619047619) "")
  (command "._LINE" (list 220.0 7880.952380952382) (list 1220.0 7880.952380952382) "")
  (command "._LINE" (list 220.0 8142.857142857143) (list 1220.0 8142.857142857143) "")
  (command "._LINE" (list 220.0 8404.761904761905) (list 1220.0 8404.761904761905) "")
  (command "._LINE" (list 220.0 8666.666666666668) (list 1220.0 8666.666666666668) "")
  (command "._LINE" (list 220.0 8928.57142857143) (list 1220.0 8928.57142857143) "")
  (command "._LINE" (list 220.0 9190.47619047619) (list 1220.0 9190.47619047619) "")
  (command "._LINE" (list 220.0 9452.380952380952) (list 1220.0 9452.380952380952) "")
  (command "._LINE" (list 220.0 9714.285714285714) (list 1220.0 9714.285714285714) "")
  (command "._LINE" (list 220.0 9976.190476190477) (list 1220.0 9976.190476190477) "")
  (command "._LINE" (list 220.0 10238.095238095239) (list 1220.0 10238.095238095239) "")
  (command "._LINE" (list 720.0 5400.0) (list 720.0 10100.0) "")
  (command "._LINE" (list 720.0 10100.0) (list 600.0 9700.0) "")
  (command "._LINE" (list 720.0 10100.0) (list 840.0 9700.0) "")
  (command "._-LAYER" "_S" "KT_TEXT" "")
  (command "._-TEXT" "_J" "_MC" (list 720.0 6200.0) 140 90 "UP (21 BAC)")
  (command "._-LAYER" "_S" "KT_TUONG_110" "")
  (command "._LINE" (list 220.0 13500.0) (list 4780.0 13500.0) "")
  (command "._LINE" (list 220.0 13610.0) (list 4780.0 13610.0) "")
  (command "._LINE" (list 2500.0 13610.0) (list 2500.0 14780.0) "")
  (command "._LINE" (list 2610.0 13610.0) (list 2610.0 14780.0) "")
  (command "._-LAYER" "_S" "KT_CUA_DI" "")
  (command "._LINE" (list 600.0 220.0) (list 4400.0 220.0) "")
  (command "._LINE" (list 600.0 160.0) (list 600.0 280.0) "")
  (command "._LINE" (list 1550.0 160.0) (list 1550.0 280.0) "")
  (command "._LINE" (list 2500.0 160.0) (list 2500.0 280.0) "")
  (command "._LINE" (list 3450.0 160.0) (list 3450.0 280.0) "")
  (command "._LINE" (list 4400.0 160.0) (list 4400.0 280.0) "")
  (command "._-LAYER" "_S" "KT_TEXT" "")
  (command "._-TEXT" "_J" "_MC" (list 2500.0 420.0) 150 0 "CUA CHINH 4 CANH (D4)")
  (command "._-LAYER" "_S" "KT_CUA_DI" "")
  (command "._LINE" (list 1600.0 13500.0) (list 1600.0 14250.0) "")
  (command "._ARC" (list 2350.0 13500.0) (list 2130.0 14030.0) (list 1600.0 14250.0))
  (command "._LINE" (list 3200.0 13500.0) (list 3200.0 14400.0) "")
  (command "._ARC" (list 4100.0 13500.0) (list 3840.0 14140.0) (list 3200.0 14400.0))
  (command "._-LAYER" "_S" "KT_CANH_QUAN" "")
  (command "._RECTANG" (list 1400.0 7000.0) (list 4780.0 9000.0))
  (command "._CIRCLE" (list 3200.0 8000.0) 350)
  (command "._CIRCLE" (list 2200.0 7600.0) 200)
  (command "._CIRCLE" (list 4200.0 8400.0) 200)
  (command "._-LAYER" "_S" "KT_NOITHAT" "")
  (command "._RECTANG" (list 2200.0 10200.0) (list 4200.0 11400.0))
  (command "._RECTANG" (list 1400.0 12300.0) (list 4780.0 13300.0))
  (command "._CIRCLE" (list 1000.0 14400.0) 180)
  (command "._RECTANG" (list 1600.0 14400.0) (list 2200.0 14800.0))
  (command "._-LAYER" "_S" "KT_TEXT" "")
  (command "._-TEXT" "_J" "_MC" (list 2500.0 1200.0) 180 0 "SAN TRUOC (12.5 m2)")
  (command "._-TEXT" "_J" "_MC" (list 2500.0 3800.0) 220 0 "PHONG KHACH DAI SANH (22.5 m2)")
  (command "._-TEXT" "_J" "_MC" (list 3200.0 8000.0) 160 0 "GIENG TROI & ZEN GARDEN")
  (command "._-TEXT" "_J" "_MC" (list 3200.0 10800.0) 200 0 "BEP & PHONG AN (22.5 m2)")
  (command "._-TEXT" "_J" "_MC" (list 1250.0 14200.0) 150 0 "WC 1 (3.5 m2)")
  (command "._-TEXT" "_J" "_MC" (list 3750.0 14200.0) 150 0 "SAN SAU (4.0 m2)")
  (command "._-LAYER" "_S" "KT_DIMS" "")
  (command "._DIMLINEAR" (list 0.0 0.0) (list 5000.0 0.0) (list 2500.0 -900.0))
  (command "._DIMLINEAR" (list 0.0 0.0) (list 0.0 2500.0) (list -900.0 1250.0))
  (command "._DIMLINEAR" (list 0.0 2500.0) (list 0.0 7000.0) (list -900.0 4750.0))
  (command "._DIMLINEAR" (list 0.0 7000.0) (list 0.0 9000.0) (list -900.0 8000.0))
  (command "._DIMLINEAR" (list 0.0 9000.0) (list 0.0 13500.0) (list -900.0 11250.0))
  (command "._DIMLINEAR" (list 0.0 13500.0) (list 0.0 15000.0) (list -900.0 14250.0))
  (command "._DIMLINEAR" (list 0.0 0.0) (list 0.0 4500.0) (list -1800.0 2250.0))
  (command "._DIMLINEAR" (list 0.0 4500.0) (list 0.0 10500.0) (list -1800.0 7500.0))
  (command "._DIMLINEAR" (list 0.0 10500.0) (list 0.0 15000.0) (list -1800.0 12750.0))
  (command "._DIMLINEAR" (list 0.0 0.0) (list 5000.0 0.0) (list 2500.0 -1800.0))
  (command "._DIMLINEAR" (list 0.0 0.0) (list 0.0 15000.0) (list -2700.0 7500.0))
  (command "._-LAYER" "_S" "KT_TEXT" "")
  (command "._-TEXT" "_J" "_MC" (list 2500.0 -2800.0) 300 0 "MẶT BẰNG TẦNG 1 - KHÁCH BẾP MỞ & TIỂU CẢNH")
  (command "._-TEXT" "_J" "_MC" (list 2500.0 -3300.0) 160 0 "CAO ĐỘ +0.000 | S = 75 m²")
  (command "._LINE" (list 500.0 -3050.0) (list 4500.0 -3050.0) "")
  ;; ----------------- TẦNG 2: MẶT BẰNG TẦNG 2 - P. NGU MASTER & CON GÁI -----------------
  (command "._-LAYER" "_S" "KT_TUONG_220" "")
  (command "._RECTANG" (list 8500.0 0.0) (list 13500.0 15000.0))
  (command "._RECTANG" (list 8720.0 220.0) (list 13280.0 14780.0))
  (command "._-LAYER" "_S" "KT_COT" "")
  (command "._RECTANG" (list 8500.0 0.0) (list 8720.0 220.0))
  (command "._LINE" (list 8500.0 0.0) (list 8720.0 220.0) "")
  (command "._LINE" (list 8720.0 0.0) (list 8500.0 220.0) "")
  (command "._RECTANG" (list 13280.0 0.0) (list 13500.0 220.0))
  (command "._LINE" (list 13280.0 0.0) (list 13500.0 220.0) "")
  (command "._LINE" (list 13500.0 0.0) (list 13280.0 220.0) "")
  (command "._RECTANG" (list 8500.0 4390.0) (list 8720.0 4610.0))
  (command "._LINE" (list 8500.0 4390.0) (list 8720.0 4610.0) "")
  (command "._LINE" (list 8720.0 4390.0) (list 8500.0 4610.0) "")
  (command "._RECTANG" (list 13280.0 4390.0) (list 13500.0 4610.0))
  (command "._LINE" (list 13280.0 4390.0) (list 13500.0 4610.0) "")
  (command "._LINE" (list 13500.0 4390.0) (list 13280.0 4610.0) "")
  (command "._RECTANG" (list 8500.0 10390.0) (list 8720.0 10610.0))
  (command "._LINE" (list 8500.0 10390.0) (list 8720.0 10610.0) "")
  (command "._LINE" (list 8720.0 10390.0) (list 8500.0 10610.0) "")
  (command "._RECTANG" (list 13280.0 10390.0) (list 13500.0 10610.0))
  (command "._LINE" (list 13280.0 10390.0) (list 13500.0 10610.0) "")
  (command "._LINE" (list 13500.0 10390.0) (list 13280.0 10610.0) "")
  (command "._RECTANG" (list 8500.0 14780.0) (list 8720.0 15000.0))
  (command "._LINE" (list 8500.0 14780.0) (list 8720.0 15000.0) "")
  (command "._LINE" (list 8720.0 14780.0) (list 8500.0 15000.0) "")
  (command "._RECTANG" (list 13280.0 14780.0) (list 13500.0 15000.0))
  (command "._LINE" (list 13280.0 14780.0) (list 13500.0 15000.0) "")
  (command "._LINE" (list 13500.0 14780.0) (list 13280.0 15000.0) "")
  (command "._-LAYER" "_S" "KT_THANG" "")
  (command "._RECTANG" (list 8720.0 5000.0) (list 9720.0 10500.0))
  (command "._LINE" (list 8720.0 5261.9047619047615) (list 9720.0 5261.9047619047615) "")
  (command "._LINE" (list 8720.0 5523.809523809524) (list 9720.0 5523.809523809524) "")
  (command "._LINE" (list 8720.0 5785.714285714286) (list 9720.0 5785.714285714286) "")
  (command "._LINE" (list 8720.0 6047.619047619048) (list 9720.0 6047.619047619048) "")
  (command "._LINE" (list 8720.0 6309.523809523809) (list 9720.0 6309.523809523809) "")
  (command "._LINE" (list 8720.0 6571.428571428572) (list 9720.0 6571.428571428572) "")
  (command "._LINE" (list 8720.0 6833.333333333334) (list 9720.0 6833.333333333334) "")
  (command "._LINE" (list 8720.0 7095.238095238095) (list 9720.0 7095.238095238095) "")
  (command "._LINE" (list 8720.0 7357.142857142857) (list 9720.0 7357.142857142857) "")
  (command "._LINE" (list 8720.0 7619.047619047619) (list 9720.0 7619.047619047619) "")
  (command "._LINE" (list 8720.0 7880.952380952382) (list 9720.0 7880.952380952382) "")
  (command "._LINE" (list 8720.0 8142.857142857143) (list 9720.0 8142.857142857143) "")
  (command "._LINE" (list 8720.0 8404.761904761905) (list 9720.0 8404.761904761905) "")
  (command "._LINE" (list 8720.0 8666.666666666668) (list 9720.0 8666.666666666668) "")
  (command "._LINE" (list 8720.0 8928.57142857143) (list 9720.0 8928.57142857143) "")
  (command "._LINE" (list 8720.0 9190.47619047619) (list 9720.0 9190.47619047619) "")
  (command "._LINE" (list 8720.0 9452.380952380952) (list 9720.0 9452.380952380952) "")
  (command "._LINE" (list 8720.0 9714.285714285714) (list 9720.0 9714.285714285714) "")
  (command "._LINE" (list 8720.0 9976.190476190477) (list 9720.0 9976.190476190477) "")
  (command "._LINE" (list 8720.0 10238.095238095239) (list 9720.0 10238.095238095239) "")
  (command "._LINE" (list 9220.0 5400.0) (list 9220.0 10100.0) "")
  (command "._LINE" (list 9220.0 10100.0) (list 9100.0 9700.0) "")
  (command "._LINE" (list 9220.0 10100.0) (list 9340.0 9700.0) "")
  (command "._-LAYER" "_S" "KT_TEXT" "")
  (command "._-TEXT" "_J" "_MC" (list 9220.0 6200.0) 140 90 "UP (21 BAC)")
  (command "._-LAYER" "_S" "KT_TUONG_110" "")
  (command "._LINE" (list 8720.0 6000.0) (list 13280.0 6000.0) "")
  (command "._LINE" (list 8720.0 6110.0) (list 13280.0 6110.0) "")
  (command "._LINE" (list 8720.0 9000.0) (list 13280.0 9000.0) "")
  (command "._LINE" (list 8720.0 9110.0) (list 13280.0 9110.0) "")
  (command "._LINE" (list 8720.0 13500.0) (list 13280.0 13500.0) "")
  (command "._LINE" (list 8720.0 13610.0) (list 13280.0 13610.0) "")
  (command "._-LAYER" "_S" "KT_CUA_DI" "")
  (command "._LINE" (list 10000.0 6000.0) (list 10000.0 5100.0) "")
  (command "._ARC" (list 10900.0 6000.0) (list 10640.0 5360.0) (list 10000.0 5100.0))
  (command "._LINE" (list 10000.0 9000.0) (list 10000.0 9900.0) "")
  (command "._ARC" (list 10900.0 9000.0) (list 10640.0 9640.0) (list 10000.0 9900.0))
  (command "._LINE" (list 10500.0 13500.0) (list 10500.0 14250.0) "")
  (command "._ARC" (list 11250.0 13500.0) (list 11030.0 14030.0) (list 10500.0 14250.0))
  (command "._-LAYER" "_S" "KT_CUA_SO" "")
  (command "._RECTANG" (list 9500.0 160.0) (list 12500.0 280.0))
  (command "._-LAYER" "_S" "KT_NOITHAT" "")
  (command "._RECTANG" (list 10100.0 3000.0) (list 11900.0 5000.0))
  (command "._RECTANG" (list 10300.0 10200.0) (list 11700.0 12200.0))
  (command "._-LAYER" "_S" "KT_TEXT" "")
  (command "._-TEXT" "_J" "_MC" (list 11000.0 700.0) 160 0 "BAN CONG XANH (6.0 m2)")
  (command "._-TEXT" "_J" "_MC" (list 11000.0 4000.0) 220 0 "P. NGU MASTER BO ME (24.0 m2)")
  (command "._-TEXT" "_J" "_MC" (list 11700.0 7500.0) 160 0 "THONG TANG GIENG TROI")
  (command "._-TEXT" "_J" "_MC" (list 11000.0 11200.0) 200 0 "P. NGU CON GAI (20.0 m2)")
  (command "._-TEXT" "_J" "_MC" (list 11000.0 14200.0) 160 0 "WC 2 & GIENG TROI SAU")
  (command "._-LAYER" "_S" "KT_DIMS" "")
  (command "._DIMLINEAR" (list 8500.0 0.0) (list 13500.0 0.0) (list 11000.0 -900.0))
  (command "._DIMLINEAR" (list 8500.0 0.0) (list 8500.0 2500.0) (list 7600.0 1250.0))
  (command "._DIMLINEAR" (list 8500.0 2500.0) (list 8500.0 7000.0) (list 7600.0 4750.0))
  (command "._DIMLINEAR" (list 8500.0 7000.0) (list 8500.0 9000.0) (list 7600.0 8000.0))
  (command "._DIMLINEAR" (list 8500.0 9000.0) (list 8500.0 13500.0) (list 7600.0 11250.0))
  (command "._DIMLINEAR" (list 8500.0 13500.0) (list 8500.0 15000.0) (list 7600.0 14250.0))
  (command "._DIMLINEAR" (list 8500.0 0.0) (list 8500.0 4500.0) (list 6700.0 2250.0))
  (command "._DIMLINEAR" (list 8500.0 4500.0) (list 8500.0 10500.0) (list 6700.0 7500.0))
  (command "._DIMLINEAR" (list 8500.0 10500.0) (list 8500.0 15000.0) (list 6700.0 12750.0))
  (command "._DIMLINEAR" (list 8500.0 0.0) (list 13500.0 0.0) (list 11000.0 -1800.0))
  (command "._DIMLINEAR" (list 8500.0 0.0) (list 8500.0 15000.0) (list 5800.0 7500.0))
  (command "._-LAYER" "_S" "KT_TEXT" "")
  (command "._-TEXT" "_J" "_MC" (list 11000.0 -2800.0) 300 0 "MẶT BẰNG TẦNG 2 - P. NGU MASTER & CON GÁI")
  (command "._-TEXT" "_J" "_MC" (list 11000.0 -3300.0) 160 0 "CAO ĐỘ +3.600 | S = 75 m²")
  (command "._LINE" (list 9000.0 -3050.0) (list 13000.0 -3050.0) "")
  ;; ----------------- TẦNG 3: MẶT BẰNG TẦNG 3 - PHÒNG THỜ & CON TRAI -----------------
  (command "._-LAYER" "_S" "KT_TUONG_220" "")
  (command "._RECTANG" (list 17000.0 0.0) (list 22000.0 15000.0))
  (command "._RECTANG" (list 17220.0 220.0) (list 21780.0 14780.0))
  (command "._-LAYER" "_S" "KT_COT" "")
  (command "._RECTANG" (list 17000.0 0.0) (list 17220.0 220.0))
  (command "._LINE" (list 17000.0 0.0) (list 17220.0 220.0) "")
  (command "._LINE" (list 17220.0 0.0) (list 17000.0 220.0) "")
  (command "._RECTANG" (list 21780.0 0.0) (list 22000.0 220.0))
  (command "._LINE" (list 21780.0 0.0) (list 22000.0 220.0) "")
  (command "._LINE" (list 22000.0 0.0) (list 21780.0 220.0) "")
  (command "._RECTANG" (list 17000.0 4390.0) (list 17220.0 4610.0))
  (command "._LINE" (list 17000.0 4390.0) (list 17220.0 4610.0) "")
  (command "._LINE" (list 17220.0 4390.0) (list 17000.0 4610.0) "")
  (command "._RECTANG" (list 21780.0 4390.0) (list 22000.0 4610.0))
  (command "._LINE" (list 21780.0 4390.0) (list 22000.0 4610.0) "")
  (command "._LINE" (list 22000.0 4390.0) (list 21780.0 4610.0) "")
  (command "._RECTANG" (list 17000.0 10390.0) (list 17220.0 10610.0))
  (command "._LINE" (list 17000.0 10390.0) (list 17220.0 10610.0) "")
  (command "._LINE" (list 17220.0 10390.0) (list 17000.0 10610.0) "")
  (command "._RECTANG" (list 21780.0 10390.0) (list 22000.0 10610.0))
  (command "._LINE" (list 21780.0 10390.0) (list 22000.0 10610.0) "")
  (command "._LINE" (list 22000.0 10390.0) (list 21780.0 10610.0) "")
  (command "._RECTANG" (list 17000.0 14780.0) (list 17220.0 15000.0))
  (command "._LINE" (list 17000.0 14780.0) (list 17220.0 15000.0) "")
  (command "._LINE" (list 17220.0 14780.0) (list 17000.0 15000.0) "")
  (command "._RECTANG" (list 21780.0 14780.0) (list 22000.0 15000.0))
  (command "._LINE" (list 21780.0 14780.0) (list 22000.0 15000.0) "")
  (command "._LINE" (list 22000.0 14780.0) (list 21780.0 15000.0) "")
  (command "._-LAYER" "_S" "KT_THANG" "")
  (command "._RECTANG" (list 17220.0 5000.0) (list 18220.0 10500.0))
  (command "._LINE" (list 17220.0 5261.9047619047615) (list 18220.0 5261.9047619047615) "")
  (command "._LINE" (list 17220.0 5523.809523809524) (list 18220.0 5523.809523809524) "")
  (command "._LINE" (list 17220.0 5785.714285714286) (list 18220.0 5785.714285714286) "")
  (command "._LINE" (list 17220.0 6047.619047619048) (list 18220.0 6047.619047619048) "")
  (command "._LINE" (list 17220.0 6309.523809523809) (list 18220.0 6309.523809523809) "")
  (command "._LINE" (list 17220.0 6571.428571428572) (list 18220.0 6571.428571428572) "")
  (command "._LINE" (list 17220.0 6833.333333333334) (list 18220.0 6833.333333333334) "")
  (command "._LINE" (list 17220.0 7095.238095238095) (list 18220.0 7095.238095238095) "")
  (command "._LINE" (list 17220.0 7357.142857142857) (list 18220.0 7357.142857142857) "")
  (command "._LINE" (list 17220.0 7619.047619047619) (list 18220.0 7619.047619047619) "")
  (command "._LINE" (list 17220.0 7880.952380952382) (list 18220.0 7880.952380952382) "")
  (command "._LINE" (list 17220.0 8142.857142857143) (list 18220.0 8142.857142857143) "")
  (command "._LINE" (list 17220.0 8404.761904761905) (list 18220.0 8404.761904761905) "")
  (command "._LINE" (list 17220.0 8666.666666666668) (list 18220.0 8666.666666666668) "")
  (command "._LINE" (list 17220.0 8928.57142857143) (list 18220.0 8928.57142857143) "")
  (command "._LINE" (list 17220.0 9190.47619047619) (list 18220.0 9190.47619047619) "")
  (command "._LINE" (list 17220.0 9452.380952380952) (list 18220.0 9452.380952380952) "")
  (command "._LINE" (list 17220.0 9714.285714285714) (list 18220.0 9714.285714285714) "")
  (command "._LINE" (list 17220.0 9976.190476190477) (list 18220.0 9976.190476190477) "")
  (command "._LINE" (list 17220.0 10238.095238095239) (list 18220.0 10238.095238095239) "")
  (command "._LINE" (list 17720.0 5400.0) (list 17720.0 10100.0) "")
  (command "._LINE" (list 17720.0 10100.0) (list 17600.0 9700.0) "")
  (command "._LINE" (list 17720.0 10100.0) (list 17840.0 9700.0) "")
  (command "._-LAYER" "_S" "KT_TEXT" "")
  (command "._-TEXT" "_J" "_MC" (list 17720.0 6200.0) 140 90 "UP (21 BAC)")
  (command "._-LAYER" "_S" "KT_TUONG_110" "")
  (command "._LINE" (list 17220.0 6000.0) (list 21780.0 6000.0) "")
  (command "._LINE" (list 17220.0 6110.0) (list 21780.0 6110.0) "")
  (command "._LINE" (list 17220.0 12000.0) (list 21780.0 12000.0) "")
  (command "._LINE" (list 17220.0 12110.0) (list 21780.0 12110.0) "")
  (command "._-LAYER" "_S" "KT_CUA_DI" "")
  (command "._LINE" (list 18500.0 6000.0) (list 18500.0 5100.0) "")
  (command "._ARC" (list 19400.0 6000.0) (list 19140.0 5360.0) (list 18500.0 5100.0))
  (command "._LINE" (list 18500.0 12000.0) (list 18500.0 11100.0) "")
  (command "._ARC" (list 19400.0 12000.0) (list 19140.0 11360.0) (list 18500.0 11100.0))
  (command "._-LAYER" "_S" "KT_NOITHAT" "")
  (command "._RECTANG" (list 18750.0 4800.0) (list 20250.0 5600.0))
  (command "._RECTANG" (list 18700.0 8500.0) (list 20300.0 10500.0))
  (command "._-LAYER" "_S" "KT_TEXT" "")
  (command "._-TEXT" "_J" "_MC" (list 19500.0 1500.0) 180 0 "SKY GARDEN SAN THUONG (12.5 m2)")
  (command "._-TEXT" "_J" "_MC" (list 19500.0 4200.0) 220 0 "PHONG THO TRANG NGHIEM (17.5 m2)")
  (command "._-TEXT" "_J" "_MC" (list 19500.0 9500.0) 220 0 "P. NGU CON TRAI (22.5 m2)")
  (command "._-TEXT" "_J" "_MC" (list 19500.0 13500.0) 180 0 "SAN PHOI & GIAT (15.0 m2)")
  (command "._-LAYER" "_S" "KT_DIMS" "")
  (command "._DIMLINEAR" (list 17000.0 0.0) (list 22000.0 0.0) (list 19500.0 -900.0))
  (command "._DIMLINEAR" (list 17000.0 0.0) (list 17000.0 2500.0) (list 16100.0 1250.0))
  (command "._DIMLINEAR" (list 17000.0 2500.0) (list 17000.0 7000.0) (list 16100.0 4750.0))
  (command "._DIMLINEAR" (list 17000.0 7000.0) (list 17000.0 9000.0) (list 16100.0 8000.0))
  (command "._DIMLINEAR" (list 17000.0 9000.0) (list 17000.0 13500.0) (list 16100.0 11250.0))
  (command "._DIMLINEAR" (list 17000.0 13500.0) (list 17000.0 15000.0) (list 16100.0 14250.0))
  (command "._DIMLINEAR" (list 17000.0 0.0) (list 17000.0 4500.0) (list 15200.0 2250.0))
  (command "._DIMLINEAR" (list 17000.0 4500.0) (list 17000.0 10500.0) (list 15200.0 7500.0))
  (command "._DIMLINEAR" (list 17000.0 10500.0) (list 17000.0 15000.0) (list 15200.0 12750.0))
  (command "._DIMLINEAR" (list 17000.0 0.0) (list 22000.0 0.0) (list 19500.0 -1800.0))
  (command "._DIMLINEAR" (list 17000.0 0.0) (list 17000.0 15000.0) (list 14300.0 7500.0))
  (command "._-LAYER" "_S" "KT_TEXT" "")
  (command "._-TEXT" "_J" "_MC" (list 19500.0 -2800.0) 300 0 "MẶT BẰNG TẦNG 3 - PHÒNG THỜ & CON TRAI")
  (command "._-TEXT" "_J" "_MC" (list 19500.0 -3300.0) 160 0 "CAO ĐỘ +7.200 | S = 75 m²")
  (command "._LINE" (list 17500.0 -3050.0) (list 21500.0 -3050.0) "")
  (command "._ZOOM" "_E")
  (setvar "CMDECHO" 1)
  (princ "\n*** DA HOAN TAT VE DAY DU TUONG 110/220, CUA VA DUONG DIM! ***\n")
  (princ)
)
(c:draw_full_townhouse)
