(defun c:draw_test ()
  (setvar "CMDECHO" 0)
  (command "._ERASE" "_ALL" "")
  (command "._-LAYER" "_M" "KT_TUONG_220" "_C" "1" "KT_TUONG_220" "")
  (command "._RECTANG" '(0 0) '(5000 15000))
  (command "._RECTANG" '(220 220) '(4780 14780))
  (command "._-LAYER" "_M" "KT_THANG" "_C" "5" "KT_THANG" "")
  (command "._RECTANG" '(220 5000) '(1220 10500))
  (command "._ZOOM" "_E")
  (setvar "CMDECHO" 1)
  (princ "\nDrawing complete!\n")
  (princ)
)
(c:draw_test)
