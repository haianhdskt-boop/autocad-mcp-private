;; ==========================================================================
;; AUTOCAD AI: DIRECT LIVE DRAFTING SCRIPT (3-FLOOR TOWNHOUSE 5x15m)
;; ==========================================================================
(defun c:draw_townhouse ()
  (setvar "CMDECHO" 0)
  (setvar "OSMODE" 0)
  (command "._ERASE" "_ALL" "")

  ;; 1. Setup Standard Layers
  (command "._-LAYER" "_M" "KT_TUONG_220" "_C" "1" "KT_TUONG_220" "")
  (command "._-LAYER" "_M" "KT_TUONG_110" "_C" "2" "KT_TUONG_110" "")
  (command "._-LAYER" "_M" "KT_COT"       "_C" "6" "KT_COT"       "")
  (command "._-LAYER" "_M" "KT_CUA_DI"    "_C" "3" "KT_CUA_DI"    "")
  (command "._-LAYER" "_M" "KT_CUA_SO"    "_C" "4" "KT_CUA_SO"    "")
  (command "._-LAYER" "_M" "KT_THANG"     "_C" "5" "KT_THANG"     "")
  (command "._-LAYER" "_M" "KT_NOITHAT"   "_C" "8" "KT_NOITHAT"   "")
  (command "._-LAYER" "_M" "KT_TEXT"      "_C" "7" "KT_TEXT"      "")
  (command "._-LAYER" "_M" "KT_DIMS"      "_C" "9" "KT_DIMS"      "")
  (command "._-LAYER" "_M" "KT_CANH_QUAN" "_C" "3" "KT_CANH_QUAN" "")

  ;; --- FLOOR 1: MAT BANG TANG 1 - KHACH BEP MO & TIEU CANH ---
  (command "._-LAYER" "_S" "KT_TUONG_220" "")
  (command "._RECTANG" (list 0.0 0.0) (list 5000.0 15000.0))
  (command "._RECTANG" (list 220.0 220.0) (list 4780.0 14780.0))
  (command "._-LAYER" "_S" "KT_COT" "")
  (command "._RECTANG" (list 0.0 0.0) (list 220.0 220.0))
  (command "._LINE" (list 0.0 0.0) (list 220.0 220.0) "")
  (command "._LINE" (list 220.0 0.0) (list 0.0 220.0) "")
  (command "._RECTANG" (list 4780.0 0.0) (list 5000.0 220.0))
  (command "._LINE" (list 4780.0 0.0) (list 5000.0 220.0) "")
  (command "._LINE" (list 5000.0 0.0) (list 4780.0 220.0) "")
  (command "._RECTANG" (list 0.0 4390.0) (list 220.0 4610.0))
  (command "._LINE" (list 0.0 4390.0) (list 220.0 4610.0) "")
  (command "._LINE" (list 220.0 4390.0) (list 0.0 4610.0) "")
  (command "._RECTANG" (list 4780.0 4390.0) (list 5000.0 4610.0))
  (command "._LINE" (list 4780.0 4390.0) (list 5000.0 4610.0) "")
  (command "._LINE" (list 5000.0 4390.0) (list 4780.0 4610.0) "")
  (command "._RECTANG" (list 0.0 10390.0) (list 220.0 10610.0))
  (command "._LINE" (list 0.0 10390.0) (list 220.0 10610.0) "")
  (command "._LINE" (list 220.0 10390.0) (list 0.0 10610.0) "")
  (command "._RECTANG" (list 4780.0 10390.0) (list 5000.0 10610.0))
  (command "._LINE" (list 4780.0 10390.0) (list 5000.0 10610.0) "")
  (command "._LINE" (list 5000.0 10390.0) (list 4780.0 10610.0) "")
  (command "._RECTANG" (list 0.0 14780.0) (list 220.0 15000.0))
  (command "._LINE" (list 0.0 14780.0) (list 220.0 15000.0) "")
  (command "._LINE" (list 220.0 14780.0) (list 0.0 15000.0) "")
  (command "._RECTANG" (list 4780.0 14780.0) (list 5000.0 15000.0))
  (command "._LINE" (list 4780.0 14780.0) (list 5000.0 15000.0) "")
  (command "._LINE" (list 5000.0 14780.0) (list 4780.0 15000.0) "")
  (command "._-LAYER" "_S" "KT_THANG" "")
  (command "._RECTANG" (list 220.0 5000.0) (list 1220.0 10500.0))
  (command "._LINE" (list 220.0 5261.9047619047615) (list 1220.0 5261.9047619047615) "")
  (command "._LINE" (list 220.0 5523.809523809524) (list 1220.0 5523.809523809524) "")
  (command "._LINE" (list 220.0 5785.714285714286) (list 1220.0 5785.714285714286) "")
  (command "._LINE" (list 220.0 6047.619047619048) (list 1220.0 6047.619047619048) "")
  (command "._LINE" (list 220.0 6309.523809523809) (list 1220.0 6309.523809523809) "")
  (command "._LINE" (list 220.0 6571.428571428572) (list 1220.0 6571.428571428572) "")
  (command "._LINE" (list 220.0 6833.333333333334) (list 1220.0 6833.333333333334) "")
  (command "._LINE" (list 220.0 7095.238095238095) (list 1220.0 7095.238095238095) "")
  (command "._LINE" (list 220.0 7357.142857142857) (list 1220.0 7357.142857142857) "")
  (command "._LINE" (list 220.0 7619.047619047619) (list 1220.0 7619.047619047619) "")
  (command "._LINE" (list 220.0 7880.952380952382) (list 1220.0 7880.952380952382) "")
  (command "._LINE" (list 220.0 8142.857142857143) (list 1220.0 8142.857142857143) "")
  (command "._LINE" (list 220.0 8404.761904761905) (list 1220.0 8404.761904761905) "")
  (command "._LINE" (list 220.0 8666.666666666668) (list 1220.0 8666.666666666668) "")
  (command "._LINE" (list 220.0 8928.57142857143) (list 1220.0 8928.57142857143) "")
  (command "._LINE" (list 220.0 9190.47619047619) (list 1220.0 9190.47619047619) "")
  (command "._LINE" (list 220.0 9452.380952380952) (list 1220.0 9452.380952380952) "")
  (command "._LINE" (list 220.0 9714.285714285714) (list 1220.0 9714.285714285714) "")
  (command "._LINE" (list 220.0 9976.190476190477) (list 1220.0 9976.190476190477) "")
  (command "._LINE" (list 220.0 10238.095238095239) (list 1220.0 10238.095238095239) "")
  (command "._LINE" (list 720.0 5400.0) (list 720.0 10100.0) "")
  (command "._LINE" (list 720.0 10100.0) (list 600.0 9700.0) "")
  (command "._LINE" (list 720.0 10100.0) (list 840.0 9700.0) "")
  (command "._-LAYER" "_S" "KT_TUONG_110" "")
  (command "._LINE" (list 220.0 13500.0) (list 4780.0 13500.0) "")
  (command "._LINE" (list 2500.0 13500.0) (list 2500.0 14780.0) "")
  (command "._-LAYER" "_S" "KT_CANH_QUAN" "")
  (command "._RECTANG" (list 1400.0 7000.0) (list 4780.0 9000.0))
  (command "._CIRCLE" (list 3200.0 8000.0) 350)
  (command "._CIRCLE" (list 2200.0 7600.0) 220)
  (command "._CIRCLE" (list 4200.0 8400.0) 220)
  (command "._-LAYER" "_S" "KT_NOITHAT" "")
  (command "._RECTANG" (list 2200.0 10200.0) (list 4200.0 11400.0))
  (command "._RECTANG" (list 1400.0 12300.0) (list 4780.0 13300.0))
  (command "._-LAYER" "_S" "KT_TEXT" "")
  (command "._-TEXT" "_J" "_MC" (list 2500.0 1200.0) 180 0 "SAN TRUOC & TIEU CANH (12.5 m2)")
  (command "._-TEXT" "_J" "_MC" (list 2500.0 3800.0) 220 0 "PHONG KHACH DAI SANH (22.5 m2)")
  (command "._-TEXT" "_J" "_MC" (list 3200.0 8000.0) 160 0 "GIENG TROI & ZEN GARDEN")
  (command "._-TEXT" "_J" "_MC" (list 3200.0 10800.0) 200 0 "BEP & PHONG AN (22.5 m2)")
  (command "._-TEXT" "_J" "_MC" (list 1250.0 14200.0) 150 0 "WC 1 (3.5 m2)")
  (command "._-TEXT" "_J" "_MC" (list 3750.0 14200.0) 150 0 "SAN SAU (4.0 m2)")
  (command "._-LAYER" "_S" "KT_DIMS" "")
  (command "._DIMLINEAR" (list 0.0 0.0) (list 5000.0 0.0) (list 2500.0 -1200.0))
  (command "._DIMLINEAR" (list 0.0 0.0) (list 0.0 15000.0) (list -1200.0 7500.0))
  (command "._-LAYER" "_S" "KT_TEXT" "")
  (command "._-TEXT" "_J" "_MC" (list 2500.0 -2200.0) 300 0 "MAT BANG TANG 1 - KHACH BEP MO & TIEU CANH")
  (command "._-TEXT" "_J" "_MC" (list 2500.0 -2700.0) 160 0 "CAO DO +0.000 | S = 75 m2")
  ;; --- FLOOR 2: MAT BANG TANG 2 - P. NGU MASTER & CON GAI ---
  (command "._-LAYER" "_S" "KT_TUONG_220" "")
  (command "._RECTANG" (list 8000.0 0.0) (list 13000.0 15000.0))
  (command "._RECTANG" (list 8220.0 220.0) (list 12780.0 14780.0))
  (command "._-LAYER" "_S" "KT_COT" "")
  (command "._RECTANG" (list 8000.0 0.0) (list 8220.0 220.0))
  (command "._LINE" (list 8000.0 0.0) (list 8220.0 220.0) "")
  (command "._LINE" (list 8220.0 0.0) (list 8000.0 220.0) "")
  (command "._RECTANG" (list 12780.0 0.0) (list 13000.0 220.0))
  (command "._LINE" (list 12780.0 0.0) (list 13000.0 220.0) "")
  (command "._LINE" (list 13000.0 0.0) (list 12780.0 220.0) "")
  (command "._RECTANG" (list 8000.0 4390.0) (list 8220.0 4610.0))
  (command "._LINE" (list 8000.0 4390.0) (list 8220.0 4610.0) "")
  (command "._LINE" (list 8220.0 4390.0) (list 8000.0 4610.0) "")
  (command "._RECTANG" (list 12780.0 4390.0) (list 13000.0 4610.0))
  (command "._LINE" (list 12780.0 4390.0) (list 13000.0 4610.0) "")
  (command "._LINE" (list 13000.0 4390.0) (list 12780.0 4610.0) "")
  (command "._RECTANG" (list 8000.0 10390.0) (list 8220.0 10610.0))
  (command "._LINE" (list 8000.0 10390.0) (list 8220.0 10610.0) "")
  (command "._LINE" (list 8220.0 10390.0) (list 8000.0 10610.0) "")
  (command "._RECTANG" (list 12780.0 10390.0) (list 13000.0 10610.0))
  (command "._LINE" (list 12780.0 10390.0) (list 13000.0 10610.0) "")
  (command "._LINE" (list 13000.0 10390.0) (list 12780.0 10610.0) "")
  (command "._RECTANG" (list 8000.0 14780.0) (list 8220.0 15000.0))
  (command "._LINE" (list 8000.0 14780.0) (list 8220.0 15000.0) "")
  (command "._LINE" (list 8220.0 14780.0) (list 8000.0 15000.0) "")
  (command "._RECTANG" (list 12780.0 14780.0) (list 13000.0 15000.0))
  (command "._LINE" (list 12780.0 14780.0) (list 13000.0 15000.0) "")
  (command "._LINE" (list 13000.0 14780.0) (list 12780.0 15000.0) "")
  (command "._-LAYER" "_S" "KT_THANG" "")
  (command "._RECTANG" (list 8220.0 5000.0) (list 9220.0 10500.0))
  (command "._LINE" (list 8220.0 5261.9047619047615) (list 9220.0 5261.9047619047615) "")
  (command "._LINE" (list 8220.0 5523.809523809524) (list 9220.0 5523.809523809524) "")
  (command "._LINE" (list 8220.0 5785.714285714286) (list 9220.0 5785.714285714286) "")
  (command "._LINE" (list 8220.0 6047.619047619048) (list 9220.0 6047.619047619048) "")
  (command "._LINE" (list 8220.0 6309.523809523809) (list 9220.0 6309.523809523809) "")
  (command "._LINE" (list 8220.0 6571.428571428572) (list 9220.0 6571.428571428572) "")
  (command "._LINE" (list 8220.0 6833.333333333334) (list 9220.0 6833.333333333334) "")
  (command "._LINE" (list 8220.0 7095.238095238095) (list 9220.0 7095.238095238095) "")
  (command "._LINE" (list 8220.0 7357.142857142857) (list 9220.0 7357.142857142857) "")
  (command "._LINE" (list 8220.0 7619.047619047619) (list 9220.0 7619.047619047619) "")
  (command "._LINE" (list 8220.0 7880.952380952382) (list 9220.0 7880.952380952382) "")
  (command "._LINE" (list 8220.0 8142.857142857143) (list 9220.0 8142.857142857143) "")
  (command "._LINE" (list 8220.0 8404.761904761905) (list 9220.0 8404.761904761905) "")
  (command "._LINE" (list 8220.0 8666.666666666668) (list 9220.0 8666.666666666668) "")
  (command "._LINE" (list 8220.0 8928.57142857143) (list 9220.0 8928.57142857143) "")
  (command "._LINE" (list 8220.0 9190.47619047619) (list 9220.0 9190.47619047619) "")
  (command "._LINE" (list 8220.0 9452.380952380952) (list 9220.0 9452.380952380952) "")
  (command "._LINE" (list 8220.0 9714.285714285714) (list 9220.0 9714.285714285714) "")
  (command "._LINE" (list 8220.0 9976.190476190477) (list 9220.0 9976.190476190477) "")
  (command "._LINE" (list 8220.0 10238.095238095239) (list 9220.0 10238.095238095239) "")
  (command "._LINE" (list 8720.0 5400.0) (list 8720.0 10100.0) "")
  (command "._LINE" (list 8720.0 10100.0) (list 8600.0 9700.0) "")
  (command "._LINE" (list 8720.0 10100.0) (list 8840.0 9700.0) "")
  (command "._-LAYER" "_S" "KT_TUONG_110" "")
  (command "._LINE" (list 8220.0 6000.0) (list 12780.0 6000.0) "")
  (command "._LINE" (list 8220.0 9000.0) (list 12780.0 9000.0) "")
  (command "._LINE" (list 8220.0 13500.0) (list 12780.0 13500.0) "")
  (command "._-LAYER" "_S" "KT_CANH_QUAN" "")
  (command "._RECTANG" (list 8200.0 200.0) (list 12800.0 1200.0))
  (command "._-LAYER" "_S" "KT_NOITHAT" "")
  (command "._RECTANG" (list 9600.0 3000.0) (list 11400.0 5000.0))
  (command "._RECTANG" (list 9800.0 10200.0) (list 11200.0 12200.0))
  (command "._-LAYER" "_S" "KT_TEXT" "")
  (command "._-TEXT" "_J" "_MC" (list 10500.0 700.0) 160 0 "BAN CONG XANH (6.0 m2)")
  (command "._-TEXT" "_J" "_MC" (list 10500.0 4000.0) 220 0 "P. NGU MASTER BO ME (24.0 m2)")
  (command "._-TEXT" "_J" "_MC" (list 11200.0 7500.0) 160 0 "THONG TANG GIENG TROI")
  (command "._-TEXT" "_J" "_MC" (list 10500.0 11200.0) 200 0 "P. NGU CON GAI (20.0 m2)")
  (command "._-TEXT" "_J" "_MC" (list 10500.0 14200.0) 160 0 "WC 2 & GIENG TROI SAU")
  (command "._-LAYER" "_S" "KT_DIMS" "")
  (command "._DIMLINEAR" (list 8000.0 0.0) (list 13000.0 0.0) (list 10500.0 -1200.0))
  (command "._DIMLINEAR" (list 8000.0 0.0) (list 8000.0 15000.0) (list 6800.0 7500.0))
  (command "._-LAYER" "_S" "KT_TEXT" "")
  (command "._-TEXT" "_J" "_MC" (list 10500.0 -2200.0) 300 0 "MAT BANG TANG 2 - P. NGU MASTER & CON GAI")
  (command "._-TEXT" "_J" "_MC" (list 10500.0 -2700.0) 160 0 "CAO DO +3.600 | S = 75 m2")
  ;; --- FLOOR 3: MAT BANG TANG 3 - PHONG THO & CON TRAI ---
  (command "._-LAYER" "_S" "KT_TUONG_220" "")
  (command "._RECTANG" (list 16000.0 0.0) (list 21000.0 15000.0))
  (command "._RECTANG" (list 16220.0 220.0) (list 20780.0 14780.0))
  (command "._-LAYER" "_S" "KT_COT" "")
  (command "._RECTANG" (list 16000.0 0.0) (list 16220.0 220.0))
  (command "._LINE" (list 16000.0 0.0) (list 16220.0 220.0) "")
  (command "._LINE" (list 16220.0 0.0) (list 16000.0 220.0) "")
  (command "._RECTANG" (list 20780.0 0.0) (list 21000.0 220.0))
  (command "._LINE" (list 20780.0 0.0) (list 21000.0 220.0) "")
  (command "._LINE" (list 21000.0 0.0) (list 20780.0 220.0) "")
  (command "._RECTANG" (list 16000.0 4390.0) (list 16220.0 4610.0))
  (command "._LINE" (list 16000.0 4390.0) (list 16220.0 4610.0) "")
  (command "._LINE" (list 16220.0 4390.0) (list 16000.0 4610.0) "")
  (command "._RECTANG" (list 20780.0 4390.0) (list 21000.0 4610.0))
  (command "._LINE" (list 20780.0 4390.0) (list 21000.0 4610.0) "")
  (command "._LINE" (list 21000.0 4390.0) (list 20780.0 4610.0) "")
  (command "._RECTANG" (list 16000.0 10390.0) (list 16220.0 10610.0))
  (command "._LINE" (list 16000.0 10390.0) (list 16220.0 10610.0) "")
  (command "._LINE" (list 16220.0 10390.0) (list 16000.0 10610.0) "")
  (command "._RECTANG" (list 20780.0 10390.0) (list 21000.0 10610.0))
  (command "._LINE" (list 20780.0 10390.0) (list 21000.0 10610.0) "")
  (command "._LINE" (list 21000.0 10390.0) (list 20780.0 10610.0) "")
  (command "._RECTANG" (list 16000.0 14780.0) (list 16220.0 15000.0))
  (command "._LINE" (list 16000.0 14780.0) (list 16220.0 15000.0) "")
  (command "._LINE" (list 16220.0 14780.0) (list 16000.0 15000.0) "")
  (command "._RECTANG" (list 20780.0 14780.0) (list 21000.0 15000.0))
  (command "._LINE" (list 20780.0 14780.0) (list 21000.0 15000.0) "")
  (command "._LINE" (list 21000.0 14780.0) (list 20780.0 15000.0) "")
  (command "._-LAYER" "_S" "KT_THANG" "")
  (command "._RECTANG" (list 16220.0 5000.0) (list 17220.0 10500.0))
  (command "._LINE" (list 16220.0 5261.9047619047615) (list 17220.0 5261.9047619047615) "")
  (command "._LINE" (list 16220.0 5523.809523809524) (list 17220.0 5523.809523809524) "")
  (command "._LINE" (list 16220.0 5785.714285714286) (list 17220.0 5785.714285714286) "")
  (command "._LINE" (list 16220.0 6047.619047619048) (list 17220.0 6047.619047619048) "")
  (command "._LINE" (list 16220.0 6309.523809523809) (list 17220.0 6309.523809523809) "")
  (command "._LINE" (list 16220.0 6571.428571428572) (list 17220.0 6571.428571428572) "")
  (command "._LINE" (list 16220.0 6833.333333333334) (list 17220.0 6833.333333333334) "")
  (command "._LINE" (list 16220.0 7095.238095238095) (list 17220.0 7095.238095238095) "")
  (command "._LINE" (list 16220.0 7357.142857142857) (list 17220.0 7357.142857142857) "")
  (command "._LINE" (list 16220.0 7619.047619047619) (list 17220.0 7619.047619047619) "")
  (command "._LINE" (list 16220.0 7880.952380952382) (list 17220.0 7880.952380952382) "")
  (command "._LINE" (list 16220.0 8142.857142857143) (list 17220.0 8142.857142857143) "")
  (command "._LINE" (list 16220.0 8404.761904761905) (list 17220.0 8404.761904761905) "")
  (command "._LINE" (list 16220.0 8666.666666666668) (list 17220.0 8666.666666666668) "")
  (command "._LINE" (list 16220.0 8928.57142857143) (list 17220.0 8928.57142857143) "")
  (command "._LINE" (list 16220.0 9190.47619047619) (list 17220.0 9190.47619047619) "")
  (command "._LINE" (list 16220.0 9452.380952380952) (list 17220.0 9452.380952380952) "")
  (command "._LINE" (list 16220.0 9714.285714285714) (list 17220.0 9714.285714285714) "")
  (command "._LINE" (list 16220.0 9976.190476190477) (list 17220.0 9976.190476190477) "")
  (command "._LINE" (list 16220.0 10238.095238095239) (list 17220.0 10238.095238095239) "")
  (command "._LINE" (list 16720.0 5400.0) (list 16720.0 10100.0) "")
  (command "._LINE" (list 16720.0 10100.0) (list 16600.0 9700.0) "")
  (command "._LINE" (list 16720.0 10100.0) (list 16840.0 9700.0) "")
  (command "._-LAYER" "_S" "KT_TUONG_110" "")
  (command "._LINE" (list 16220.0 6000.0) (list 20780.0 6000.0) "")
  (command "._LINE" (list 16220.0 12000.0) (list 20780.0 12000.0) "")
  (command "._-LAYER" "_S" "KT_CANH_QUAN" "")
  (command "._RECTANG" (list 16200.0 200.0) (list 20800.0 2500.0))
  (command "._CIRCLE" (list 17200.0 1200.0) 250)
  (command "._CIRCLE" (list 19800.0 1200.0) 250)
  (command "._-LAYER" "_S" "KT_NOITHAT" "")
  (command "._RECTANG" (list 17750.0 4800.0) (list 19250.0 5600.0))
  (command "._RECTANG" (list 17700.0 8500.0) (list 19300.0 10500.0))
  (command "._-LAYER" "_S" "KT_TEXT" "")
  (command "._-TEXT" "_J" "_MC" (list 18500.0 1500.0) 180 0 "SKY GARDEN SAN THUONG (12.5 m2)")
  (command "._-TEXT" "_J" "_MC" (list 18500.0 4200.0) 220 0 "PHONG THO TRANG NGHIEM (17.5 m2)")
  (command "._-TEXT" "_J" "_MC" (list 18500.0 9500.0) 220 0 "P. NGU CON TRAI (22.5 m2)")
  (command "._-TEXT" "_J" "_MC" (list 18500.0 13500.0) 180 0 "SAN PHOI & GIAT (15.0 m2)")
  (command "._-LAYER" "_S" "KT_DIMS" "")
  (command "._DIMLINEAR" (list 16000.0 0.0) (list 21000.0 0.0) (list 18500.0 -1200.0))
  (command "._DIMLINEAR" (list 16000.0 0.0) (list 16000.0 15000.0) (list 14800.0 7500.0))
  (command "._-LAYER" "_S" "KT_TEXT" "")
  (command "._-TEXT" "_J" "_MC" (list 18500.0 -2200.0) 300 0 "MAT BANG TANG 3 - PHONG THO & CON TRAI")
  (command "._-TEXT" "_J" "_MC" (list 18500.0 -2700.0) 160 0 "CAO DO +7.200 | S = 75 m2")
  (command "._ZOOM" "_E")
  (setvar "CMDECHO" 1)
  (princ "\n*** DA VE HOAN TAT 3 TANG NHA PHO 5x15m TREN AUTOCAD! ***\n")
  (princ)
)
(c:draw_townhouse)
